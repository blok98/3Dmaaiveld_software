FME workspace lod31citygml_ams.fmw

Parameters:
- SourceDataset_LAS = $(FME_MF_DIR)input_laz/schollenbrugstraat_limit.laz   # Source ASPRS LAS File(s)
- SourceDataset_OGCGEOPACKAGE = $(FME_MF_DIR)input_bgt/schollenbrugstraat.gpkg   # GeoPackage File
- DestDataset_CITYJSON = $(FME_MF_DIR)output/cityjson/road_lod3.json   # Destination CityJSON File

Readers:
- LAS_1: LAS from $(SourceDataset_LAS)
- OGCGEOPACKAGE_1: OGCGEOPACKAGE from $(SourceDataset_OGCGEOPACKAGE)

Writers:
- CITYJSON_1: CITYJSON to $(DestDataset_CITYJSON) in EPSG:7415

Note: Schollenbrugstraat_limit [.LAZ] (AHN4)
Note: Ruimtelijke fout AHN4: / xy = 8cm / z = 5cm
LAS (reader LAS_1)
    -> Clipper_2 [CLIPPEE]
Note: SpatialFilter : Filter
Junction_3
    -> Junction_4
Note: multi clip las
Clipper_2
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> Clipper [CLIPPEE]
    INSIDE -> Clipper_4 [CLIPPEE]
    INSIDE -> Junction_2
Junction_2
    -> Counter_5
Counter_5
    CNT_ATTR = _countPoints
    GROUP_BY = lokaalid
    SCOPE = Local
    START = 0
    -> TINGenerator [POINTS/LINES] [off]
    -> Counter_5_Output
Note: buitenring/binnenring: / alleen de buitenkant
Counter_5_Output: Inspector

Bookmark: Input Schollenbrugstraat
overpass_bridge_onbegroeidterreindeelactueelbestaand (reader OGCGEOPACKAGE_1)
    attributes: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
overpass_bridge_overbruggingsdeelactueelbestaand_pijler (reader OGCGEOPACKAGE_1)
    attributes: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
overpass_bridge_ondersteunendwegdeelactueelbestaand (reader OGCGEOPACKAGE_1)
    attributes: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
terrain_begroeidterreindeelactueelbestaand_0 (reader OGCGEOPACKAGE_1) [off]
    attributes: gml_id text, namespace text, lokaalid text, objectbegintijd date, objecteindtijd date, tijdstipregistratie datetime, eindregistratie datetime, lv_publicatiedatum datetime, bronhouder text, inonderzoek boolean, relatievehoogteligging mediumint, bgt_status text, plus_status text, bgt_fysiekvoorkomen text, plus_fysiekvoorkomen text, begroeidterreindeeloptalud boolean, ogc_fid int,PrimaryKey
    -> Densifier [off]
    -> Clipper_2 [CLIPPER] [off]
    -> Junction_3 [off]
terrain_onbegroeidterreindeelactueelbestaand_0 (reader OGCGEOPACKAGE_1) [off]
    attributes: gml_id text, namespace text(8), lokaalid text(38), objectbegintijd date, objecteindtijd date, tijdstipregistratie datetime, eindregistratie datetime, lv_publicatiedatum datetime, bronhouder text(5), inonderzoek boolean, relatievehoogteligging mediumint, bgt_status text(255), plus_status text(255), bgt_fysiekvoorkomen text(255), plus_fysiekvoorkomen text(255), onbegroeidterreindeeloptalud boolean, fid int,PrimaryKey
    -> Densifier
    -> Clipper_2 [CLIPPER]
    -> Junction_3 [off]
terrain_ondersteunendwaterdeelactueelbestaand_0 (reader OGCGEOPACKAGE_1) [off]
    attributes: gml_id text, namespace text(8), lokaalid text(38), objectbegintijd date, objecteindtijd date, tijdstipregistratie datetime, eindregistratie datetime, lv_publicatiedatum datetime, bronhouder text(5), inonderzoek boolean, relatievehoogteligging mediumint, bgt_status text(255), plus_status text(255), bgt_type text(255), plus_type text(255), fid int,PrimaryKey
    -> Densifier
    -> Clipper_2 [CLIPPER]
    -> Junction_3
road_ondersteunendwegdeelactueelbestaand_0 (reader OGCGEOPACKAGE_1) [off]
    attributes: gml_id text, namespace text(8), lokaalid text(38), objectbegintijd date, objecteindtijd date, tijdstipregistratie datetime, eindregistratie datetime, lv_publicatiedatum datetime, bronhouder text(5), inonderzoek boolean, relatievehoogteligging mediumint, bgt_status text(255), plus_status text(255), bgt_functie text(255), plus_functie text(255), bgt_fysiekvoorkomen text(255), plus_fysiekvoorkomen text(255), ondersteunendwegdeeloptalud boolean, fid int,PrimaryKey
    -> Densifier
    -> Clipper_2 [CLIPPER]
    -> Junction_3
building_overigbouwwerkactueelbestaand_0 (reader OGCGEOPACKAGE_1)
    attributes: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
overpass_bridge_begroeidterreindeelactueelbestaand (reader OGCGEOPACKAGE_1)
    attributes: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
road_wegdeelactueelbestaand_0 (reader OGCGEOPACKAGE_1)
    attributes: gml_id text, namespace text(8), lokaalid text(38), objectbegintijd date, objecteindtijd date, tijdstipregistratie datetime, eindregistratie datetime, lv_publicatiedatum datetime, bronhouder text(5), inonderzoek boolean, relatievehoogteligging mediumint, bgt_status text(255), plus_status text(255), bgt_functie text(255), plus_functie text(255), bgt_fysiekvoorkomen text(255), plus_fysiekvoorkomen text(255), wegdeeloptalud boolean, fid int,PrimaryKey
    -> Densifier
    -> Clipper_2 [CLIPPER]
    -> Junction_3
water_waterdeelactueelbestaand_0 (reader OGCGEOPACKAGE_1)
    attributes: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
building_pandactueelbestaand_0 (reader OGCGEOPACKAGE_1)
    attributes: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
forest_begroeidterreindeelactueelbestaand (reader OGCGEOPACKAGE_1)
    attributes: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
separation_scheidingactueelbestaand_0 (reader OGCGEOPACKAGE_1)
    attributes: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
overpass_bridge_wegdeelactueelbestaand (reader OGCGEOPACKAGE_1)
    attributes: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

Bookmark: Voorbereiding vlakken
Note: 1 punt toevoegen tussen 2 vertices
Densifier
    INTERVAL = 1
    MODE = Uniform Interval
    DENSIFIED -> DonutHoleExtractor
DonutHoleExtractor
    DEAGGREGATE_INPUT = Yes
    OUTERSHELL -> Chopper
    HOLE -> Counter_2
Note: Gaten teller
Counter_2
    CNT_ATTR = _count_donut
    DOMAIN = @Value(lokaalid)
    SCOPE = Local
    START = 0
    -> Chopper
Chopper
    DEAGGREGATE_INPUT = Deaggregate
    MAX_VERTICES = 1
    MODE = By Vertex
    REMNANT_ATTR = _remnant
    CHOPPED -> Counter
Counter
    CNT_ATTR = _count
    DOMAIN = @Value(lokaalid)
    SCOPE = Local
    START = 0
    -> UUIDGenerator

Bookmark: bereken hoogte per vertex
Note: maak "pointid" attribuut
UUIDGenerator
    UUID_ATTR = pointid
    -> Bufferer
    -> FeatureMerger [REQUESTOR]
Note: Buffer = 0.3 m
Bufferer
    ANGLE = 22.5
    CAP_STYLE = Round
    CORNER_STYLE = Round
    MODE = AREA
    OFFSET = 0.3
    OFFSET_UNITS = NONE
    BUFFERED -> Clipper [CLIPPER]
Clipper
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    GROUP_BY = lokaalid
    LINES_AS_SEGMENTS = No
    MEASURE_TYPE = Continuous
    MISSING_VAL_MODE = Compute
    PRESERVE_CLIPPEE_EXTENTS = No
    VAL_SOURCE = Clippee Only
    INSIDE -> PointCloudStatisticsCalculator
Note: z = mean
PointCloudStatisticsCalculator
    POINT_COMPONENTS = "z   MEAN      intensity        "
    -> FeatureMerger [SUPPLIER]
Note: koppelen met z-mean
FeatureMerger
    ATTR_ACCUM_MODE = Merge Supplier
    ATTR_CONFLICT_RES = Use Requestor
    IGNORE_NULLS = No
    JOIN_KEYS = @Value(pointid) @Value(pointid) AUTO
    MERGE_TYPE = Attributes Only
    PROCESS_DUPS = NO
    REJECT_NULL_MISSING_KEYS = No
    SUPPLIERS_FIRST = No
    MERGED -> 3DForcer
    UNMERGED_REQUESTOR -> Bufferer_2
    UNMERGED_REQUESTOR -> FeatureMerger_6 [REQUESTOR]

Bookmark: Voeg punten toe aan vlak
Note: Tester_4 : Passed
Junction_4
    -> SpatialFilter [Filter]
Note: Surface Model cannot be constructed with 3 points / TINGenerator (SurfaceModelFactory): Group 110: Failed to initialize the Surface Model
Note: surface tolarance = 0.3
TINGenerator
    GROUP_BY = lokaalid
    TOLERANCE = 0.05
    TIN_SURFACE -> GeometryCoercer
Note: Naar intern geometry format + xquery
GeometryCoercer
    GQUERY:
      for $geom in //geometry
      where $geom/count(parent::geometry) = 0
      return number($geom/@fme_id)
    KIND = fme_composite_surface
    COERCED -> Deaggregator_2
Note: uitelkaar trekken
Deaggregator_2
    EXPLODE_INSTANCES = Yes
    GEOM_NAME_FIELD = _geometry_name
    LIST_ATTR_MODE_LOOKUP = LEAN
    MODE = Flatten All Levels
    SPLIT_COMPOSITES = Yes
    DEAGGREGATED -> GeometryCoercer_2
Note: poly's maken
GeometryCoercer_2
    GQUERY:
      for $geom in //geometry
      where $geom/count(parent::geometry) = 0
      return number($geom/@fme_id)
    KIND = fme_polygon
    COERCED -> UUIDGenerator_4
Note: toevoegen 'vlakid'
UUIDGenerator_4
    UUID_ATTR = vlakid
    -> CenterPointReplacer
    -> FeatureMerger_7 [REQUESTOR]
CenterPointReplacer
    POINTTYPE = INSIDE
    POINT -> SpatialFilter [Candidate]
Note: SpatialFilter = Contains
SpatialFilter
    AGGREGATE_HANDLING = Yes
    ATTR_ACCUM_MODE = Merge Filter
    ATTR_CONFLICT_RES = Use Candidate
    BASE_TYPE = Multiple Filters
    CURVE_BOUNDARY_RULE_PARAM = Default Rule
    GROUP_BY = lokaalid
    PASS_CRITERIA = Pass Against One Filter
    PREDATTR = _predicate
    PREDICATES = CONTAINS
    USE_BOUNDING_BOX = No
    PASSED -> FeatureMerger_7 [SUPPLIER]
Note: vlakid's mergen
FeatureMerger_7
    ATTR_ACCUM_MODE = Merge Supplier
    ATTR_CONFLICT_RES = Use Requestor
    IGNORE_NULLS = No
    JOIN_KEYS = @Value(vlakid) @Value(vlakid) AUTO
    MERGE_TYPE = Attributes Only
    PROCESS_DUPS = NO
    REJECT_NULL_MISSING_KEYS = No
    SUPPLIERS_FIRST = No
    MERGED -> AttributeKeeper_5
Note: kiezen welke atrributen meegaan
AttributeKeeper_5
    CREATE_BULK_MODE_FEATURES = NO
    KEEP_ATTRS = lokaalid,vlakid,begroeidterreindeeloptalud,bgt_functie,bgt_fysiekvoorkomen,bgt_status,bgt_type,bronhouder,eindregistratie,gml_id,inonderzoek,lv_publicatiedatum,namespace,objectbegintijd,objecteindtijd,ogc_fid,onbegroeidterreindeeloptalud,ondersteunendwegdeeloptalud,plus_functie,plus_fysiekvoorkomen,plus_status,plus_type,relatievehoogteligging,tijdstipregistratie,wegdeeloptalud
    -> Orientor
Note: Orientatie poly naar linksom zetten (why?)
Orientor
    KIND = LEFT_HAND_RULE
    ORIENTED -> Counter_3

Bookmark: berken hoogte per vertex met extra grote buffer
Note: Bufferer = 3m
Bufferer_2
    ANGLE = 22.5
    CAP_STYLE = Round
    CORNER_STYLE = Round
    MODE = AREA
    OFFSET = 3
    OFFSET_UNITS = NONE
    BUFFERED -> Clipper_4 [CLIPPER]
Clipper_4
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    GROUP_BY = lokaalid
    LINES_AS_SEGMENTS = No
    MEASURE_TYPE = Continuous
    MISSING_VAL_MODE = Compute
    PRESERVE_CLIPPEE_EXTENTS = No
    VAL_SOURCE = Clippee Only
    INSIDE -> PointCloudStatisticsCalculator_2
Note: z = mean
PointCloudStatisticsCalculator_2
    POINT_COMPONENTS = "z   MEAN      intensity        "
    -> FeatureMerger_6 [SUPPLIER]
FeatureMerger_6
    ATTR_ACCUM_MODE = Merge Supplier
    ATTR_CONFLICT_RES = Use Requestor
    IGNORE_NULLS = No
    JOIN_KEYS = @Value(pointid) @Value(pointid) AUTO
    MERGE_TYPE = Attributes Only
    PROCESS_DUPS = NO
    REJECT_NULL_MISSING_KEYS = No
    SUPPLIERS_FIRST = No
    MERGED -> 3DForcer

Bookmark: Hertsel vlakkenin 3D
Note: optrekken op basis van z.mean
3DForcer
    KEEPZVAL = No
    ZVALATTR = @Value(z.mean)
    -> Sorter_3
Sorter_3
    SORT_PARM = lokaalid ALPHA ASCENDING _count NUMERIC ASCENDING
    SORTED -> LineBuilder
Note: group by _count_donut en lokaalid
LineBuilder
    ACCUM_INPUT_ATTRS = Use Attributes From One Feature
    GROUP_BY = _count_donut lokaalid
    REMOVE_DUPLICATES = No
    POLYGON -> Tester
Tester
    BOOL_OP = OR
    TEST_CLAUSE = TEST _count_donut ATTRIBUTE_HAS_A_VALUE ""
    TEST_MODE = TEST
    PASSED -> Clipper_3 [CLIPPER]
    FAILED -> Clipper_3 [CLIPPEE]
Clipper_3
    BOUNDARY_CASES = Treat as Inside
    CLEANING_TOLERANCE = Automatic
    CLIPPED_ATTR = _clipped
    CLIP_TYPE = Multiple Clippers
    GROUP_BY = lokaalid
    LINES_AS_SEGMENTS = No
    MEASURE_TYPE = Continuous
    MISSING_VAL_MODE = Compute
    PRESERVE_CLIPPEE_EXTENTS = No
    VAL_SOURCE = Clippee Only
    OUTSIDE -> TINGenerator [POINTS/LINES]
    OUTSIDE -> Chopper_2
    OUTSIDE -> TINGenerator [BREAKLINES]

Bookmark: Verticale randen
Note: chop by 2 vertices
Chopper_2
    DEAGGREGATE_INPUT = Deaggregate
    MAX_VERTICES = 2
    MODE = By Vertex
    REMNANT_ATTR = _remnant
    CHOPPED -> UUIDGenerator_2
Note: lineid
UUIDGenerator_2
    UUID_ATTR = lineid
    -> LineOnLineOverlayer [LINE]
    -> BoundsExtractor
LineOnLineOverlayer
    ATTRS_ACCUM_MODE = Use Attributes From One Feature
    CLEANING_TOLERANCE = Automatic
    DEAGGREGATE_INPUT = Yes
    GENERATE_LIST_DROP = YES
    LIST_ATTRS_TO_INCLUDE = lineid
    LIST_NAME = overlap
    OV_ATTR = _overlaps
    SEPARATE_COLLINEAR_SEGMENTS = No
    LINE -> TestFilter
TestFilter
    DEFAULT_VALUE = <UNFILTERED>
    PASSED_TEST_GROUP_OUTPUT = FIRST
    TEST_LIST = "BOOL_OP,OR,COMPOSITE_TEST,""""""1"""""",TEST_CLAUSE,TEST @Value(_overlaps) = 1",1,"BOOL_OP,OR,COMPOSITE_TEST,""""""1"""""",TEST_CLAUSE,TEST @Value(_overlaps) = 2",2
    2 -> UUIDGenerator_3
Note: overlapid
UUIDGenerator_3
    UUID_ATTR = overlapid
    -> AttributeKeeper_4
Note: Alles mee
AttributeKeeper_4
    CREATE_BULK_MODE_FEATURES = NO
    KEEP_ATTRS = overlap{1}.lineid,overlap{0}.lineid,overlapid,_clipped,_count,_count_donut,_fme_no_clipper,_overlaps,_remnant,begroeidterreindeeloptalud,bgt_functie,bgt_fysiekvoorkomen,bgt_status,bgt_type,bronhouder,eindregistratie,fid,fme_basename,fme_feature_type,gml_id,inonderzoek,lineid,lokaalid,lv_publicatiedatum,namespace,objectbegintijd,objecteindtijd,ogc_fid,onbegroeidterreindeeloptalud,ondersteunendwegdeeloptalud,overlap{0}.direction,plus_functie,plus_fysiekvoorkomen,plus_status,plus_type,pointid,relatievehoogteligging,tijdstipregistratie,wegdeeloptalud,z.mean
    -> FeatureMerger_3 [SUPPLIER]
    -> FeatureMerger_2 [SUPPLIER]
Note: min/max z attributen
BoundsExtractor
    ZMAX = _zmax
    ZMIN = _zmin
    -> AttributeCreator_2
Note: gemiddelde van z.min en z.max
AttributeCreator_2
    ATTR_TABLE = SET_TO average_height = @Evaluate(@average(@Value(_zmax),@Value(_zmin)))
    -> FeatureMerger_2 [REQUESTOR]
FeatureMerger_2
    ATTR_ACCUM_MODE = Merge Supplier
    ATTR_CONFLICT_RES = Use Requestor
    IGNORE_NULLS = No
    JOIN_KEYS = @Value(lineid) @Value(overlap{0}.lineid) AUTO
    MERGE_TYPE = Attributes Only
    PROCESS_DUPS = NO
    REJECT_NULL_MISSING_KEYS = No
    SUPPLIERS_FIRST = No
    MERGED -> Sorter_2
    UNMERGED_REQUESTOR -> FeatureMerger_3 [REQUESTOR]
    <REJECTED> -> Junction_6
Note: join_op_lineid_en_overlap_1_.lineid
FeatureMerger_3
    ATTR_ACCUM_MODE = Merge Supplier
    ATTR_CONFLICT_RES = Use Requestor
    IGNORE_NULLS = No
    JOIN_KEYS = @Value(lineid) @Value(overlap{1}.lineid) AUTO
    MERGE_TYPE = Attributes Only
    PROCESS_DUPS = NO
    REJECT_NULL_MISSING_KEYS = No
    SUPPLIERS_FIRST = No
    MERGED -> Sorter_2
    <REJECTED> -> Junction_5
Note: _Desc
Sorter_2
    SORT_PARM = average_height NUMERIC DESCENDING
    SORTED -> Chopper_3
Note: opdelen per vertex
Chopper_3
    DEAGGREGATE_INPUT = Deaggregate
    MAX_VERTICES = 1
    MODE = By Vertex
    REMNANT_ATTR = _remnant
    CHOPPED -> LineBuilder_2
LineBuilder_2
    ACCUM_INPUT_ATTRS = Use Attributes From One Feature
    GROUP_BY = overlapid
    REMOVE_DUPLICATES = No
    LINE -> LineCloser
    POLYGON -> Chopper_4
Note: first win
LineCloser
    CONNECT_Z_MODE = First Wins
    AREA -> Junction
Note: opdelen per vertex
Chopper_4
    DEAGGREGATE_INPUT = Deaggregate
    MAX_VERTICES = 1
    MODE = By Vertex
    REMNANT_ATTR = _remnant
    CHOPPED -> Counter_4
Note: count overlaps
Counter_4
    CNT_ATTR = _count_overlaps
    DOMAIN = @Value(overlapid)
    SCOPE = Global
    START = 0
    -> Tester_2
Note: # overlaps = 0
Tester_2
    BOOL_OP = OR
    TEST_CLAUSE = TEST @Value(_count_overlaps) = 0
    TEST_MODE = TEST
    PASSED -> Sorter
    PASSED -> AttributeManager_4
    FAILED -> Sorter
AttributeManager_4
    -> Sorter
Sorter
    SORT_PARM = overlapid ALPHA ASCENDING _count_overlaps NUMERIC ASCENDING
    SORTED -> LineBuilder_3
LineBuilder_3
    ACCUM_INPUT_ATTRS = Use Attributes From One Feature
    GROUP_BY = overlapid
    REMOVE_DUPLICATES = No
    POLYGON -> Junction
Junction
    -> Counter_3
Junction_5
Junction_6

Bookmark: CityGML voorbereiding
Note: lokaalid tellertje
Counter_3
    CNT_ATTR = count_lokaalid
    DOMAIN = @Value(lokaalid)
    SCOPE = Global
    START = 0
    -> Aggregator_2
Note: op lokaalid
Aggregator_2
    ACCUM_ATTRS_NAME = Use Attributes From One Feature
    AGGREGATE_TYPE = Homogeneous Collection (If Possible)
    GROUP_BY = lokaalid
    MODE = Geometry - Assemble One Level
    SEP = ,
    AGGREGATE -> AttributeCreator
Note: AttributeCreator gml_parent_id = Roads
AttributeCreator
    ATTR_TABLE = SET_TO gml_parent_id = Road
    -> AttributeKeeper
Note: Overbodige kolommen weg
AttributeKeeper
    CREATE_BULK_MODE_FEATURES = NO
    KEEP_ATTRS = gml_id,lokaalid,average_height,begroeidterreindeeloptalud,bgt_fysiekvoorkomen,bgt_status,bronhouder,count_lokaalid,lineid,lv_publicatiedatum,namespace,objectbegintijd,objecteindtijd,plus_fysiekvoorkomen,plus_status,pointid,relatievehoogteligging,tijdstipregistratie,bgt_functie,bgt_type,eindregistratie,inonderzoek,onbegroeidterreindeeloptalud,ondersteunendwegdeeloptalud,plus_functie,plus_type,wegdeeloptalud,gml_parent_id
    -> Tester_3
Note: filter op bgt_functie
Note: mapping voor traffic area?
Tester_3
    BOOL_OP = OR
    TEST_CLAUSE:
      TEST @Value(bgt_functie) = Rijbaan
      TEST @Value(bgt_functie) = Rijwielpad
      TEST @Value(bgt_functie) = Voetpad
      TEST @Value(bgt_functie) = Parkeerplaats
      TEST @Value(bgt_functie) = Verkeersdrempel
    TEST_MODE = TEST
    PASSED -> Aggregator

Bookmark: CityGML Road
Note: gml_parent_id heb ik per ongeluk weggegooid
Aggregator
    ACCUM_ATTRS_NAME = Use Attributes From One Feature
    AGGREGATE_TYPE = Homogeneous Collection (If Possible)
    GROUP_BY = gml_parent_id
    MODE = Geometry - Assemble One Level
    SEP = ,
    AGGREGATE -> AttributeKeeper_6
Note: Overbodige kolommen weg
AttributeKeeper_6
    CREATE_BULK_MODE_FEATURES = NO
    KEEP_ATTRS = gml_id,lokaalid,average_height,begroeidterreindeeloptalud,bgt_fysiekvoorkomen,bgt_status,bronhouder,count_lokaalid,lv_publicatiedatum,namespace,objectbegintijd,objecteindtijd,plus_fysiekvoorkomen,plus_status,relatievehoogteligging,tijdstipregistratie,bgt_functie,bgt_type,eindregistratie,inonderzoek,onbegroeidterreindeeloptalud,ondersteunendwegdeeloptalud,plus_functie,plus_type,wegdeeloptalud
    -> GeometryRemover
GeometryRemover
    -> CityGMLGeometrySetter_3
Note: stond op lod2MultiSurface, nu op lod3
CityGMLGeometrySetter_3
    GEOM = lod3MultiSurface
    ROLE = boundedBy
    -> Road (writer CITYJSON_1)
    -> CityGMLGeometrySetter_3_Output
Note: epsg:7415
Note: Road: [CITYJSON] versie 1.01
Road (writer CITYJSON_1)
    attributes: citygml_lod_name string, citygml_feature_role string, lokaalid string, gml_id string, namespace string, objectbegintijd string, objecteindtijd string, tijdstipregistratie string, eindregistratie string, lv_publicatiedatum string, bronhouder string, inonderzoek logical, relatievehoogteligging int32, bgt_status string, plus_status string, bgt_fysiekvoorkomen string, plus_fysiekvoorkomen string, begroeidterreindeeloptalud logical, onbegroeidterreindeeloptalud logical, bgt_type string, plus_type string, bgt_functie string, plus_functie string, wegdeeloptalud logical, ondersteunendwegdeeloptalud logical, average_height string, count_lokaalid real64
CityGMLGeometrySetter_3_Output: Inspector
AttributeManager
    ATTR_TABLE:
      REMOVE gml_parent_id
      REMOVE pointid
      REMOVE lineid
      REMOVE count_lokaalid

Bookmark: CityGML Traffic Area
AttributeManager_2
    ATTR_TABLE:
      REMOVE fid
      SET_TO citygml_usage = FME_CONDITIONAL:DEFAULT_VALUE'_FME_NO_OP_'BOOL_OP;OR;COMPOSITE_TEST;1 OR 2 OR 3;TEST @Value(KLASSE) = Rijbaan;TEST @Value(KLASSE) = Parkeerplaats;TEST @Value(KLASSE) = Verkeersdrempel'2'BOOL_OP;OR;COMPOSITE_TEST;1;TEST @Value(KLASSE) = Voetpad'1'BOOL_OP;OR;COMPOSITE_TEST;1;TEST @Value(KLASSE) = Rijwielpad'6'FME_NUM_CONDITIONS4___
      SET_TO citygml_function = FME_CONDITIONAL:DEFAULT_VALUE'_FME_NO_OP_'BOOL_OP;OR;COMPOSITE_TEST;1 OR 2;TEST @Value(KLASSE) = Rijbaan;TEST @Value(KLASSE) = Verkeersdrempel'1'BOOL_OP;OR;COMPOSITE_TEST;1;TEST @Value(KLASSE) = Voetpad'2'BOOL_OP;OR;COMPOSITE_TEST;1;TEST @Value(KLASSE) = Rijwielpad'3'BOOL_OP;OR;COMPOSITE_TEST;1;TEST @Value(KLASSE) = Parkeerplaats'6'FME_NUM_CONDITIONS5___
      SET_TO citygml_surfaceMaterial = FME_CONDITIONAL:DEFAULT_VALUE'_FME_NO_OP_'BOOL_OP;OR;COMPOSITE_TEST;1;TEST @Value(FYSIEKVK) = gesloten verharding'1'BOOL_OP;OR;COMPOSITE_TEST;1;TEST @Value(FYSIEKVK) = open verharding'3'FME_NUM_CONDITIONS3___
    -> AttributeRemover_2
    -> ListBuilder_2
AttributeRemover_2
    REMOVE_ATTRS = citygml_usage,citygml_function,citygml_surfaceMaterial
    -> FeatureMerger_5 [REQUESTOR]
ListBuilder_2
    GROUP_BY = DGDT_ID
    LIST_ATTRS_TO_INCLUDE = citygml_function citygml_usage citygml_surfaceMaterial
    LIST_NAME = citygml
    -> ListRenamer_2
ListRenamer_2
    LEAVE_ORIG = No
    LIST_ACTION = Rename
    LIST_COMPONENT_NAMES = citygml{},citygml_function{},citygml_function,
    LIST_NAME = citygml{}.citygml_function
    -> ListRenamer_3
ListRenamer_3
    LEAVE_ORIG = No
    LIST_ACTION = Rename
    LIST_COMPONENT_NAMES = citygml{},citygml_usage{},citygml_usage,
    LIST_NAME = citygml{}.citygml_usage
    -> ListRenamer_5
ListRenamer_5
    LEAVE_ORIG = No
    LIST_ACTION = Rename
    LIST_COMPONENT_NAMES = citygml{},citygml_surfaceMaterial{},citygml_surfaceMaterial,
    LIST_NAME = citygml{}.citygml_surfaceMaterial
    -> AttributeKeeper_3
AttributeKeeper_3
    CREATE_BULK_MODE_FEATURES = No
    KEEP_ATTRS = DGDT_ID,citygml_function{0},citygml_surfaceMaterial{0},citygml_usage{0}
    -> FeatureMerger_5 [SUPPLIER]
FeatureMerger_5
    ATTR_ACCUM_MODE = Merge Supplier
    ATTR_CONFLICT_RES = Use Requestor
    IGNORE_NULLS = No
    JOIN_KEYS = @Value(DGDT_ID) @Value(DGDT_ID) AUTO
    MERGE_TYPE = Attributes Only
    PROCESS_DUPS = NO
    REJECT_NULL_MISSING_KEYS = No
    SUPPLIERS_FIRST = No
    MERGED -> CityGMLGeometrySetter
CityGMLGeometrySetter
    GEOM = lod2MultiSurface
    ROLE = trafficArea

Bookmark: CityGML Auxiliary Traffic Area
AttributeManager_3
    ATTR_TABLE:
      SET_TO citygml_function = FME_CONDITIONAL:DEFAULT_VALUE'_FME_NO_OP_'BOOL_OP;OR;COMPOSITE_TEST;1;TEST @Value(KLASSE) = Verkeerseiland'1300'BOOL_OP;OR;COMPOSITE_TEST;1;TEST @Value(KLASSE) = Gras'1020'FME_NUM_CONDITIONS3___
      SET_TO citygml_surfaceMaterial = FME_CONDITIONAL:DEFAULT_VALUE'_FME_NO_OP_'BOOL_OP;OR;COMPOSITE_TEST;1;TEST @Value(KLASSE) = Gras'10'BOOL_OP;OR;COMPOSITE_TEST;1;TEST @Value(KLASSE) = Verkeerseiland'3'FME_NUM_CONDITIONS3___
    -> ListBuilder
    -> AttributeRemover
AttributeRemover
    REMOVE_ATTRS = citygml_function,citygml_surfaceMaterial
    -> FeatureMerger_4 [REQUESTOR]
ListBuilder
    GROUP_BY = DGDT_ID
    LIST_ATTRS_TO_INCLUDE = citygml_function citygml_surfaceMaterial
    LIST_NAME = citygml
    -> ListRenamer
ListRenamer
    LEAVE_ORIG = No
    LIST_ACTION = Rename
    LIST_COMPONENT_NAMES = citygml{},citygml_function{},citygml_function,
    LIST_NAME = citygml{}.citygml_function
    -> ListRenamer_4
ListRenamer_4
    LEAVE_ORIG = No
    LIST_ACTION = Rename
    LIST_COMPONENT_NAMES = citygml{},citygml_surfaceMaterial{},citygml_surfaceMaterial,
    LIST_NAME = citygml{}.citygml_surfaceMaterial
    -> AttributeKeeper_2
AttributeKeeper_2
    CREATE_BULK_MODE_FEATURES = No
    KEEP_ATTRS = DGDT_ID,citygml_function{0},citygml_surfaceMaterial{0}
    -> FeatureMerger_4 [SUPPLIER]
FeatureMerger_4
    ATTR_ACCUM_MODE = Merge Supplier
    ATTR_CONFLICT_RES = Use Requestor
    IGNORE_NULLS = No
    JOIN_KEYS = @Value(DGDT_ID) @Value(DGDT_ID) AUTO
    MERGE_TYPE = Attributes Only
    PROCESS_DUPS = NO
    REJECT_NULL_MISSING_KEYS = No
    SUPPLIERS_FIRST = No
    MERGED -> CityGMLGeometrySetter_2
CityGMLGeometrySetter_2
    GEOM = lod2MultiSurface
    ROLE = auxiliaryTrafficArea

FME custom transformer CityGMLGeometrySetter
This transformer provides a convenient way to set both the CityGML LOD Name and role from a preset list of options.
Input Ports
    Input
    Features to tag with City LOD name and feature role 
    Output Ports
    Output
    Features tagged with City LOD name and feature role 
    Parameters
    CityGML Lod Name
    Select the desired CityGML Lod name
    Feature Role
    Select the desired feature role

Parameters:
- GEOM =   # CityGML Lod Name
- ROLE =   # Feature Role

Input (input)
    -> AttributeCreator
Note: Set LOD name / and citygml role
AttributeCreator
    ATTR_TABLE:
      SET_TO citygml_lod_name = $(GEOM)
      SET_TO citygml_feature_role = $(ROLE)
    -> GeometryPropertySetter
Note: Convert LOD to geometry trait
GeometryPropertySetter
    GQUERY:
      for $geom in //geometry
      where $geom/count(parent::geometry) = 0
      return number($geom/@fme_id)
    OVERWRITE_CHOICE = Yes
    REMOVE_ATTRIBUTE = No
    SETTYPE_PARAM = Traits From Attributes
    SRC_ATTRS = citygml_lod_name
    SET -> Output (output)
Output (output)
